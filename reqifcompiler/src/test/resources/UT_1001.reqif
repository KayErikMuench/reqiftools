# test
RequieTool export

# Specification: Spec
- ID: Test-Specification

## Chapter 1 (HeadlineType)

### REQ_1 (ConfigurationSpecObjectType)
Hello
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- Status: StatusTest
- Priority: RankingTest
- Risk: RankingTest
