# test
RequieTool export

# Specification: Spec
- ID: Test-Specification

## Chapter 1 (HeadlineType)

### REQ_1 (ConfigurationSpecObjectType)
Hello
- Status: StatusTest
- Priority: RankingTest
- Risk: RankingTest
- SpecRelationType -> REQ_2

## Chapter 2 (HeadlineType)

### Section 2.2 (HeadlineType)

#### REQ_2 (ConfigurationSpecObjectType)
Hello
- Status: StatusTest
- Priority: RankingTest
- Risk: RankingTest
